#!/usr/bin/env python
# -*- coding: utf-8 -*-

# ====================================================================================
# ====================================================================================
# ==                                                                                ==
# ==                               Simple grid                                      ==
# ==                                                                                ==
# ====================================================================================
# ====================================================================================
# ABOUT
# ====================================================================================
# version v1.0
# Macro developed for FreeCAD (http://www.freecadweb.org/).
# This macro toggles a configurable grid in plane XY as helper for 3D view navigation
#
# LICENSE
# ====================================================================================
# Copyright (c) 2019 Pablo Gil Fernandez
#
# This work is licensed under GNU Lesser General Public License (LGPL).
# To view a copy of this license, visit https://www.gnu.org/licenses/lgpl-3.0.html
#
# ====================================================================================
__title__   = "Simple grid"
__author__  = "Pablo Gil Fernández"
__version__ = "1.0"
__date__    = "11/08/2019"

__Comment__ = "This macro toggles a configurable grid in plane XY as helper for 3D view navigation."

__Wiki__ = "https://www.freecadweb.org/wiki/Simple_grid"
__Help__ = ""
__Status__ = "stable"
__Requires__ = "freecad 0.17"

import FreeCAD, FreeCADGui, Draft
from PySide import QtGui # for clearing the console

def a_clear_console():
    #clearing previous messages
    mw=FreeCADGui.getMainWindow()
    # c=mw.findChild(QtGui.QPlainTextEdit, "Python console")
    # c.clear()
    r=mw.findChild(QtGui.QTextEdit, "Report view")
    r.clear()
#if not Mod_ENABLED:
a_clear_console()

# Variables ====================================
size_x = 100 # only correct spacing_x steps will be created (when divided by 2 it must be integer)
size_y = 100 # only correct spacing_y steps will be created (when divided by 2 it must be integer)
spacing_x = 10
spacing_y = 10
line_width = 2.0
axis_width = line_width * 2
line_color = (0.5, 0.5, 0.5)
x_axis_color = (0.7, 0.3, 0.3)
y_axis_color = (0.3, 0.7, 0.3)
globalAxisCross = False
groupName = 'Grid'


# Main toggle ====================================
if len(App.ActiveDocument.getObjectsByLabel(groupName)) == 0: # if grid doesn't exist create it
    App.ActiveDocument.addObject("App::DocumentObjectGroup",groupName)

    # Global document axis ====================================
    Gui.ActiveDocument.ActiveView.setAxisCross(globalAxisCross)

    pl = FreeCAD.Placement()
    pl.Rotation.Q = (0.0,0.0,0.0,1.0)

    # Lines step correction ====================================f
    lines_x = int(size_x / spacing_x)
    center_x = int(lines_x /2) + 1
    if lines_x % 2 == 0:
        lines_x += 1 # if number of lines is even it must change to odd
    lines_y = int(size_y / spacing_y)
    center_y = int(lines_y /2) + 1
    if lines_y % 2 == 0:
        lines_y += 1 # if number of lines is even it must change to odd

    # X secondary lines ====================================
    i = 1
    while i <= lines_x:
        from_vector = FreeCAD.Vector(-(lines_y - 1) * spacing_y / 2,(i-1) * spacing_x - (lines_x - center_x)*spacing_x,0.0)
        to_vector = FreeCAD.Vector((lines_y - 1) * spacing_y / 2,(i-1) * spacing_x - (lines_x - center_x)*spacing_x,0.0)
        pl.Base = from_vector
        points = [pl.Base,to_vector]
        line = Draft.makeWire(points,placement=pl,closed=False,face=True,support=None)
        #Draft.autogroup(line)
        line.Label = "xline_" + str(i)
        App.ActiveDocument.getObjectsByLabel(line.Label)[0].ViewObject.LineWidth = line_width
        App.ActiveDocument.getObjectsByLabel(line.Label)[0].ViewObject.LineColor = line_color
        App.ActiveDocument.getObjectsByLabel(line.Label)[0].ViewObject.PointColor = line_color
        App.ActiveDocument.getObjectsByLabel(line.Label)[0].ViewObject.Selectable = False
        App.ActiveDocument.getObject(groupName).addObject(App.ActiveDocument.getObjectsByLabel(line.Label)[0])
        i += 1

    # Y secondary lines ====================================
    i = 1
    while i <= lines_y:
        from_vector = FreeCAD.Vector((i-1) * spacing_y - (lines_y - center_y)*spacing_y, -(lines_x - 1) * spacing_x / 2, 0.0)
        to_vector = FreeCAD.Vector((i-1) * spacing_y - (lines_y - center_y)*spacing_y, (lines_x - 1) * spacing_x / 2, 0.0)
        pl.Base = from_vector
        points = [pl.Base,to_vector]
        line = Draft.makeWire(points,placement=pl,closed=False,face=True,support=None)
        #Draft.autogroup(line)
        line.Label = "yline_" + str(i)
        App.ActiveDocument.getObjectsByLabel(line.Label)[0].ViewObject.LineWidth = line_width
        App.ActiveDocument.getObjectsByLabel(line.Label)[0].ViewObject.LineColor = line_color
        App.ActiveDocument.getObjectsByLabel(line.Label)[0].ViewObject.PointColor = line_color
        App.ActiveDocument.getObjectsByLabel(line.Label)[0].ViewObject.Selectable = False
        App.ActiveDocument.getObject(groupName).addObject(App.ActiveDocument.getObjectsByLabel(line.Label)[0])
        i += 1

    # X Axis ====================================
    App.ActiveDocument.getObjectsByLabel("xline_" + str(center_x))[0].ViewObject.LineWidth = axis_width
    App.ActiveDocument.getObjectsByLabel("xline_" + str(center_x))[0].ViewObject.LineColor = x_axis_color
    App.ActiveDocument.getObjectsByLabel("xline_" + str(center_x))[0].ViewObject.PointColor = x_axis_color

    # Y Axis ====================================
    App.ActiveDocument.getObjectsByLabel("yline_" + str(center_y))[0].ViewObject.LineWidth = axis_width
    App.ActiveDocument.getObjectsByLabel("yline_" + str(center_y))[0].ViewObject.LineColor = y_axis_color
    App.ActiveDocument.getObjectsByLabel("yline_" + str(center_y))[0].ViewObject.PointColor = y_axis_color

    #  ====================================
    FreeCAD.ActiveDocument.recompute()
    Gui.ActiveDocument.getObject(groupName).Visibility=False # trick to hide it at the first try in the Model hierarchy
    Gui.ActiveDocument.getObject(groupName).Visibility=True # trick to hide it at the first try in the Model hierarchy

    print("Grid enabled: a " + str(int((lines_x - 1) * spacing_x)) + "x" + str(int((lines_y - 1) * spacing_y)) + " grid has successfully been created")
else:
    App.ActiveDocument.getObject(groupName).removeObjectsFromDocument() # if grid exists remove it
    App.ActiveDocument.removeObject(groupName)
    print("Grid disabled")
